# reqs

## FSR1: Activate when signalled. (Functional)
The brake lamps shall be activated within 50ms of receiving a brake signal.

### SYSR1: Monitor brake signal. (Functional)
The brake signal shall be monitored in a cycle lower than 50ms.

### SYSR2: Activate brakes even with a minor failure. (Functional)
If the monitored brake signal value differs from the logic unit calculated value by more than 10%, and the logic output is to enable the brake lamps, the brake lamps shall be illuminated.

## FSR2: Activate when accelerating negatively. (Functional)
The brake lamps shall be activated if the acceleration of the vehicle is measured to be > 1.3 m/s2 while the vehicle is in regenerative braking (one pedal) mode and shall remain activated until the acceleration is measured to be <= 1.2 m/s2, or when the measured pressure on the brake pedal is below 40% maximum depression.

### SYSR3: Accelerometer will be monitored. (Functional)
The acceleration of the vehicle shall be monitored in a cycle lower than 50ms using an accelerometer.

### SYSR4: Compare acceleration and velocity derivation. (Functional)
The vehicle acceleration shall be compared with the calculated acceleration derived from velocity, in the logic unit, in a cycle lower than 50ms.

## FSR3: Logic unit detects faults in itself. (Functional)
Faults in the logic unit or brake lamps, which would lead to an unintended activation of brake lamps, shall be detected within 50ms and a message will be displayed to the user.

### SYSR5: Activate brakes even if logic fails while accel is right. (Functional)
If the acceleration of the vehicle is measured to be within the brake lamp activation range, and the driving mode is regenerative braking, and the logic unit does not assert that the brake lights are to be activated, the brake lights shall be activated

### SYSR6: Display error if stuck on. (Functional)
The logic unit shall detect faults within itself or the brake lamps, which would result in the unintended activation of brake lamps within 50ms and provide a message to the driver display with the code “ErBrkON”, which the display controller may interpret.

## FSR4: Logic unit detects unintended non-illumination. (Functional)
Faults in the logic unit or brake lamps, which would lead to a failure to illuminate, shall be detected within 50ms and a message will be displayed to the user.

### SYSR7: Display error if stuck off. (Functional)
The logic unit shall detect faults within itself or the brake lamps, which would result in failure to illuminate brake lamps when the brake signal is active within 50 ms and provide a message to the driver display with the code “ErBrkOFF”, which the display controller may interpret.
